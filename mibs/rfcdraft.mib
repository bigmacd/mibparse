-- MIB created 5/08/96 10:16:42, by
--   SMIC (the next generation) version 1.6.29, November 22, 1994.

DS1-MIB DEFINITIONS ::= BEGIN

-- From file: "rfcdraft.mi2"

IMPORTS
    Gauge32
            FROM SNMPv2-SMI-v1
    OBJECT-TYPE
            FROM RFC-1212
    TRAP-TYPE
            FROM RFC-1215
    DisplayString, TimeStamp, TruthValue
            FROM SNMPv2-TC-v1
    InterfaceIndex
            FROM IF-MIB
    transmission
            FROM RFC1213-MIB;

ds1 OBJECT IDENTIFIER ::= { transmission 18 }
-- MODULE-IDENTITY
--  LastUpdated
--    9602032200Z
--  OrgName
--    IETF Trunk MIB Working Group
--  ContactInfo
--            David Fowler
--    
--     Postal: Newbridge Networks Corporation
--             600 March Road
--             Kanata, Ontario, Canada K2K 2E6
--    
--             Tel: +1 613 591 3600
--             Fax: +1 613 591 3680
--    
--          E-mail: davef@newbridge.com
--  Descr
--    The MIB module to describe DS1, E1, DS2, and
--     E2 interfaces objects.

ds1Traps        OBJECT IDENTIFIER ::= { ds1 15 }
ds1Conformance  OBJECT IDENTIFIER ::= { ds1 14 }
ds1Groups       OBJECT IDENTIFIER ::= { ds1Conformance 1 }
ds1Compliances  OBJECT IDENTIFIER ::= { ds1Conformance 2 }

dsx1ConfigTable OBJECT-TYPE
    SYNTAX SEQUENCE OF Dsx1ConfigEntry
    ACCESS not-accessible
    STATUS mandatory
    DESCRIPTION
        "The DS1 Configuration table."
    ::= { ds1 6 }

dsx1ConfigEntry OBJECT-TYPE
    SYNTAX Dsx1ConfigEntry
    ACCESS not-accessible
    STATUS mandatory
    DESCRIPTION
        "An entry in the DS1 Configuration table."
    INDEX { dsx1LineIndex }
    ::= { dsx1ConfigTable 1 }

Dsx1ConfigEntry ::= SEQUENCE {
    dsx1LineIndex InterfaceIndex,
    dsx1IfIndex InterfaceIndex,
    dsx1TimeElapsed INTEGER,
    dsx1ValidIntervals INTEGER,
    dsx1LineType INTEGER,
    dsx1LineCoding INTEGER,
    dsx1SendCode INTEGER,
    dsx1CircuitIdentifier DisplayString,
    dsx1LoopbackConfig INTEGER,
    dsx1LineStatus INTEGER,
    dsx1SignalMode INTEGER,
    dsx1TransmitClockSource INTEGER,
    dsx1Fdl INTEGER,
    dsx1InvalidIntervals INTEGER,
    dsx1LineLength INTEGER,
    dsx1LineStatusLastChange TimeStamp,
    dsx1LineStatusChangeTrapEnable INTEGER
    }

dsx1LineIndex OBJECT-TYPE
    SYNTAX InterfaceIndex
--    Rsyntax Integer32
    ACCESS read-only
    STATUS mandatory
    DESCRIPTION
        "This object should be made equal to ifIndex.  The
        next paragraph describes its previous usage.
        Making the object equal to ifIndex allows proper
        use of ifStackTable and ds0/ds0bundle mibs.
        
        Previously, this object is the identifier of a DS1
        Interface on a managed device.  If there is an
        ifEntry that is directly associated with this and
        only this DS1 interface, it should have the same
        value as ifIndex.  Otherwise, number the
        dsx1LineIndices with an unique identifier
        following the rules of choosing a number that is
        greater than ifNumber and numbering the inside
        interfaces (e.g., equipment side) with even
        numbers and outside interfaces (e.g, network side)
        with odd numbers."
    ::= { dsx1ConfigEntry 1 }

dsx1IfIndex OBJECT-TYPE
    SYNTAX InterfaceIndex
--    Rsyntax Integer32
    ACCESS read-only
    STATUS deprecated
    DESCRIPTION
        "This value for this object is equal to the value
        of ifIndex from the Interfaces table of MIB II
        (RFC 1213)."
    ::= { dsx1ConfigEntry 2 }

dsx1TimeElapsed OBJECT-TYPE
    SYNTAX INTEGER(0..899)
    ACCESS read-only
    STATUS mandatory
    DESCRIPTION
        "The number of seconds that have elapsed since the
        beginning of the near end current error-
        measurement period."
    ::= { dsx1ConfigEntry 3 }

dsx1ValidIntervals OBJECT-TYPE
    SYNTAX INTEGER(0..96)
    ACCESS read-only
    STATUS mandatory
    DESCRIPTION
        "The number of previous near end intervals for
        which valid data was collected.  The value will be
        96 unless the interface was brought online within
        the last 24 hours, in which case the value will be
        the number of complete 15 minute near end
        intervals since the interface has been online.  In
        the case where the agent is a proxy, it is
        possible that some intervals are unavailable.  In
        this case, this interval is the maximum interval
        number for which valid data is available."
    ::= { dsx1ConfigEntry 4 }

dsx1LineType OBJECT-TYPE
    SYNTAX INTEGER {
        other(1),
        dsx1ESF(2),
        dsx1D4(3),
        dsx1E1(4),
        dsx1E1CRC(5),
        dsx1E1MF(6),
        dsx1E1CRCMF(7),
        dsx1Unframed(8),
        dsx1E1Unframed(9)
        }
    ACCESS read-write
    STATUS mandatory
    DESCRIPTION
        "This variable indicates  the  variety  of  DS1
        Line  implementing  this  circuit.  The type of
        circuit affects the number of bits  per  second
        that  the circuit can reasonably carry, as well
        as the interpretation of the  usage  and  error
        statistics.  The values, in sequence, describe:
        
        TITLE:         SPECIFICATION:
        dsx1ESF         Extended SuperFrame DS1
        dsx1D4          AT&T D4 format DS1
        dsx1E1          CCITT Recommendation G.704
                         (Table 4a)
        dsx1E1-CRC      CCITT Recommendation G.704
                         (Table 4b)
        dsxE1-MF        G.704 (Table 4a) with TS16
                         multiframing enabled
        dsx1E1-CRC-MF   G.704 (Table 4b) with TS16
                         multiframing enabled
        dsx1Unframed    No Framing performed
        dsx1E1Unframed  E1 with No Framing
        
        dsx1E1Unframed - E1, no framing = 32 x 64k = 2048k
        dsx1E1 or dsx1E1CRC - E1, with framing,
           no signalling = 31 x 64k = 1984k
        dsx1E1MF or dsx1E1CRCMF - E1, with framing,
           signalling = 30 x 64k = 1920k
        
        For further information See CCITT Recomm G.704"
    ::= { dsx1ConfigEntry 5 }

dsx1LineCoding OBJECT-TYPE
    SYNTAX INTEGER {
        dsx1JBZS(1),
        dsx1B8ZS(2),
        dsx1HDB3(3),
        dsx1ZBTSI(4),
        dsx1AMI(5),
        other(6)
        }
    ACCESS read-write
    STATUS mandatory
    DESCRIPTION
        "This variable describes the variety of Zero Code
        Suppression used on this interface, which in turn
        affects a number of its characteristics.
        
        dsx1JBZS refers the Jammed Bit Zero Suppression,
        in  which  the  AT&T specification of at least one
        pulse every 8 bit periods is literally implemented
        by forcing a pulse in bit 8 of each channel.
        Thus, only seven bits per  channel, or 1.344 Mbps,
        is available for data.
        
        dsx1B8ZS refers to the use of a specified  pattern
        of  normal  bits  and  bipolar violations which
        are used to replace a sequence  of  eight zero
        bits.
        
        ANSI Clear Channels may use dsx1ZBTSI, or  Zero
        Byte Time Slot Interchange.
        
        E1 links, with or without CRC, use dsx1HDB3  or
        dsx1AMI.
        
        dsx1AMI refers to a mode wherein no  zero  code
        suppression  is  present  and the line encoding
        does not solve the problem directly.   In  this
        application, the higher layer must provide data
        which meets or exceeds the  pulse  density
        requirements, such as inverting HDLC data."
    ::= { dsx1ConfigEntry 6 }

dsx1SendCode OBJECT-TYPE
    SYNTAX INTEGER {
        dsx1SendNoCode(1),
        dsx1SendLineCode(2),
        dsx1SendPayloadCode(3),
        dsx1SendResetCode(4),
        dsx1SendQRS(5),
        dsx1Send511Pattern(6),
        dsx1Send3in24Pattern(7),
        dsx1SendOtherTestPattern(8)
        }
    ACCESS read-write
    STATUS mandatory
    DESCRIPTION
        "This variable indicates what type of code is
        being sent across the DS1 interface by the device.
        Setting this variable causes the interface to send
        the code requested.  The values mean:
        dsx1SendNoCode
        sending looped or normal data
        
        dsx1SendLineCode
        sending a request for a line loopback
        
        dsx1SendPayloadCode
        sending a request for a payload loopback
        
        dsx1SendResetCode
        sending a loopback termination request
        
        dsx1SendQRS
        sending a Quasi-Random Signal  (QRS)  test
        pattern
        
        dsx1Send511Pattern
        sending a 511 bit fixed test pattern
        
        dsx1Send3in24Pattern
        sending a fixed test pattern of 3 bits set
        in 24
        
        dsx1SendOtherTestPattern
        sending a test pattern  other  than  those
        described by this object"
    ::= { dsx1ConfigEntry 7 }

dsx1CircuitIdentifier OBJECT-TYPE
    SYNTAX DisplayString(SIZE(0..255))
--    Rsyntax OCTET STRING(SIZE(0..255))
    ACCESS read-write
    STATUS deprecated
    DESCRIPTION
        "This variable contains the transmission vendor's
        circuit identifier, for the purpose of
        facilitating troubleshooting.  In the presence of
        interface layering, ifPhysAddress is now
        sufficient for all previous usages of
        dsx1CircuitIndentifier."
    ::= { dsx1ConfigEntry 8 }

dsx1LoopbackConfig OBJECT-TYPE
    SYNTAX INTEGER {
        dsx1NoLoop(1),
        dsx1PayloadLoop(2),
        dsx1LineLoop(3),
        dsx1OtherLoop(4),
        dsxInwardLoop(5)
        }
    ACCESS read-write
    STATUS mandatory
    DESCRIPTION
        "This variable represents the loopback configuration
        of the DS1 interface.  Agents supporting read/write
        access should return badValue in response to a
        requested loopback state that the interface does not
        support.  The values mean:
        
        dsx1NoLoop
          Not in the loopback state.  A device that is
          not capable of performing a loopback on
          the interface shall always return this as
          it's value.
        
        dsx1PayloadLoop
          The received signal at this interface is looped
          through the device.  Typically the received signal
          is looped back for retransmission after it has
          passed through the device's framing function.
        
        dsx1LineLoop
          The received signal at this interface does not
          go through the device (minimum penetration) but
          is looped back out.
        
        dsx1OtherLoop
          Loopbacks that are not defined here.
        
        dsx1InwardLoop
          The transmitted signal at this interface is looped
          back and received by the same interface.  What is
          transmitted onto the line is product dependent."
    ::= { dsx1ConfigEntry 9 }

dsx1LineStatus OBJECT-TYPE
    SYNTAX INTEGER(1..131071)
    ACCESS read-only
    STATUS mandatory
    DESCRIPTION
        "This variable indicates the Line Status of the
        interface.  It contains loopback, failure,
        received 'alarm' and transmitted 'alarms
        information.
        
        The dsx1LineStatus is a bit map represented as a
        sum, therefore, it can represent multiple failures
        (alarms) and a LoopbackState simultaneously.
        
        dsx1NoAlarm must be set if and only if no other
        flag is set.
        
        If the dsx1loopbackState bit is set, the loopback
        in effect can be determined from the
        dsx1loopbackConfig object.
        The various bit positions are:
        1     dsx1NoAlarm           No alarm present
        2     dsx1RcvFarEndLOF      Far end LOF (a.k.a., Yellow Alarm)
        4     dsx1XmtFarEndLOF      Near end sending LOF Indication
        8     dsx1RcvAIS            Far end sending AIS
        16     dsx1XmtAIS            Near end sending AIS
        32     dsx1LossOfFrame       Near end LOF (a.k.a., Red Alarm)
        64     dsx1LossOfSignal      Near end Loss Of Signal
        128     dsx1LoopbackState     Near end is looped
        256     dsx1T16AIS            E1 TS16 AIS
        512     dsx1RcvFarEndLOMF     Far End Sending TS16 LOMF
        1024     dsx1XmtFarEndLOMF     Near End Sending TS16 LOMF
        2048     dsx1RcvTestCode       Near End detects a test code
        4096     dsx1OtherFailure      any line status not defined here
        8192     dsx1UnavailSigState   Near End in Unavailable Signal
                         State
        16384     dsx1NetEquipOOS       Carrier Equipment Out of Service
        32768     dsx1RcvPayloadAIS     DS2 Payload AIS
        65536     dsx1Ds2PerfThreshold  DS2 Performance Threshold
                         Exceeded"
    ::= { dsx1ConfigEntry 10 }

dsx1SignalMode OBJECT-TYPE
    SYNTAX INTEGER {
        none(1),
        robbedBit(2),
        bitOriented(3),
        messageOriented(4),
        other(5)
        }
    ACCESS read-write
    STATUS mandatory
    DESCRIPTION
        "'none' indicates that no bits are reserved for
        signaling on this channel.
        
        'robbedBit' indicates that DS1 Robbed Bit  Sig-
        naling is in use.
        
        'bitOriented' indicates that E1 Channel  Asso-
        ciated Signaling is in use.
        
        'messageOriented' indicates that Common  Chan-
        nel Signaling is in use either on channel 16 of
        an E1 link or channel 24 of a DS1."
    ::= { dsx1ConfigEntry 11 }

dsx1TransmitClockSource OBJECT-TYPE
    SYNTAX INTEGER {
        loopTiming(1),
        localTiming(2),
        throughTiming(3)
        }
    ACCESS read-write
    STATUS mandatory
    DESCRIPTION
        "The source of Transmit Clock.
         'loopTiming' indicates that the recovered re-
        ceive clock is used as the transmit clock.
        
         'localTiming' indicates that a local clock
        source is used.
        
         'throughTiming' indicates that recovered re-
        ceive clock from another interface is used as
        the transmit clock."
    ::= { dsx1ConfigEntry 12 }

dsx1Fdl OBJECT-TYPE
    SYNTAX INTEGER(1..15)
    ACCESS read-write
    STATUS mandatory
    DESCRIPTION
        "This bitmap describes the use of  the  facili-
        ties data link, and is the sum of the capabili-
        ties.  Set any bits that are appropriate:
        
        other(1),
        dsx1AnsiT1403(2),
        dsx1Att54016(4),
        dsx1FdlNone(8)
        
         'other' indicates that a protocol  other  than
        one following is used.
        
         'dsx1AnsiT1403' refers to the  FDL  exchange
        recommended by ANSI.
        
         'dsx1Att54016' refers to ESF FDL exchanges.
         'dsx1FdlNone' indicates that the device  does
        not use the FDL."
    ::= { dsx1ConfigEntry 13 }

dsx1InvalidIntervals OBJECT-TYPE
    SYNTAX INTEGER(0..96)
    ACCESS read-only
    STATUS mandatory
    DESCRIPTION
        "The number of intervals for which no valid data
        is available."
    ::= { dsx1ConfigEntry 14 }

dsx1LineLength OBJECT-TYPE
    SYNTAX INTEGER(0..64000)
--  Units
--    meters
    ACCESS read-only
    STATUS mandatory
    DESCRIPTION
        "The length of the ds1 line in meters. This
        objects provides information for line build out
        circuitry if it exists and can profitably use the
        information."
    ::= { dsx1ConfigEntry 15 }

dsx1LineStatusLastChange OBJECT-TYPE
    SYNTAX TimeStamp
--    Rsyntax TimeTicks
    ACCESS read-only
    STATUS mandatory
    DESCRIPTION
        "The value of MIB II's sysUpTime object at the
        time this DS1 entered its current line status
        state.  If the current state was entered prior to
        the last re-initialization of the proxy-agent,
        then this object contains a zero value."
    ::= { dsx1ConfigEntry 16 }

dsx1LineStatusChangeTrapEnable OBJECT-TYPE
    SYNTAX INTEGER {
        enabled(1),
        disabled(2)
        }
    ACCESS read-write
    STATUS mandatory
    DESCRIPTION
        "Indicates whether dsx1LineStatusChange traps
        should be generated for this interface."
    DEFVAL { disabled }
    ::= { dsx1ConfigEntry 17 }

dsx1CurrentTable OBJECT-TYPE
    SYNTAX SEQUENCE OF Dsx1CurrentEntry
    ACCESS not-accessible
    STATUS mandatory
    DESCRIPTION
        "The DS1 current table contains various statistics
        being collected for the current 15 minute
        interval."
    ::= { ds1 7 }

dsx1CurrentEntry OBJECT-TYPE
    SYNTAX Dsx1CurrentEntry
    ACCESS not-accessible
    STATUS mandatory
    DESCRIPTION
        "An entry in the DS1 Current table."
    INDEX { dsx1CurrentIndex }
    ::= { dsx1CurrentTable 1 }

Dsx1CurrentEntry ::= SEQUENCE {
    dsx1CurrentIndex InterfaceIndex,
    dsx1CurrentESs Gauge32,
    dsx1CurrentSESs Gauge32,
    dsx1CurrentSEFSs Gauge32,
    dsx1CurrentUASs Gauge32,
    dsx1CurrentCSSs Gauge32,
    dsx1CurrentPCVs Gauge32,
    dsx1CurrentLESs Gauge32,
    dsx1CurrentBESs Gauge32,
    dsx1CurrentDMs Gauge32,
    dsx1CurrentLCVs Gauge32
    }

dsx1CurrentIndex OBJECT-TYPE
    SYNTAX InterfaceIndex
--    Rsyntax Integer32
    ACCESS read-only
    STATUS mandatory
    DESCRIPTION
        "The index value which uniquely identifies  the
        DS1  interface  to which this entry is applicable.
        The interface identified by a  particular value
        of  this  index is the same interface as
        identified by the same value as a dsx1LineIndex
        object instance."
    ::= { dsx1CurrentEntry 1 }

dsx1CurrentESs OBJECT-TYPE
    SYNTAX Gauge32
    ACCESS read-only
    STATUS mandatory
    DESCRIPTION
        "The number of Errored Seconds, encountered  by a
        DS1 interface in the current 15 minute interval.
        noSuchInstance will be returned if no data is
        available."
    ::= { dsx1CurrentEntry 2 }

dsx1CurrentSESs OBJECT-TYPE
    SYNTAX Gauge32
    ACCESS read-only
    STATUS mandatory
    DESCRIPTION
        "The number of Severely Errored Seconds
        encountered by  a  DS1  interface  in the current
        15 minute interval. noSuchInstance will be
        returned if no data is available."
    ::= { dsx1CurrentEntry 3 }

dsx1CurrentSEFSs OBJECT-TYPE
    SYNTAX Gauge32
    ACCESS read-only
    STATUS mandatory
    DESCRIPTION
        "The number of Severely Errored Framing Seconds
        encountered  by  a DS1 interface in the current 15
        minute interval. noSuchInstance will be returned
        if no data is available."
    ::= { dsx1CurrentEntry 4 }

dsx1CurrentUASs OBJECT-TYPE
    SYNTAX Gauge32
    ACCESS read-only
    STATUS mandatory
    DESCRIPTION
        "The number of Unavailable Seconds  encountered by
        a DS1 interface in the current 15 minute interval.
        noSuchInstance will be returned if no data is
        available."
    ::= { dsx1CurrentEntry 5 }

dsx1CurrentCSSs OBJECT-TYPE
    SYNTAX Gauge32
    ACCESS read-only
    STATUS mandatory
    DESCRIPTION
        "The number of Controlled Slip Seconds
        encountered  by a  DS1  interface  in the current
        15 minute interval. noSuchInstance will be
        returned if no data is available."
    ::= { dsx1CurrentEntry 6 }

dsx1CurrentPCVs OBJECT-TYPE
    SYNTAX Gauge32
    ACCESS read-only
    STATUS mandatory
    DESCRIPTION
        "The number of Path Coding  Violations
        encountered by  a  DS1  interface  in the current
        15 minute interval. noSuchInstance will be
        returned if no data is available."
    ::= { dsx1CurrentEntry 7 }

dsx1CurrentLESs OBJECT-TYPE
    SYNTAX Gauge32
    ACCESS read-only
    STATUS mandatory
    DESCRIPTION
        "The number of Line Errored Seconds encountered by
        a DS1 interface in the current 15 minute interval.
        noSuchInstance will be returned if no data is
        available."
    ::= { dsx1CurrentEntry 8 }

dsx1CurrentBESs OBJECT-TYPE
    SYNTAX Gauge32
    ACCESS read-only
    STATUS mandatory
    DESCRIPTION
        "The number of Bursty  Errored  Seconds  (BESs)
        encountered  by  a DS1 interface in the current 15
        minute interval. noSuchInstance will be returned
        if no data is available."
    ::= { dsx1CurrentEntry 9 }

dsx1CurrentDMs OBJECT-TYPE
    SYNTAX Gauge32
    ACCESS read-only
    STATUS mandatory
    DESCRIPTION
        "The number of Degraded Minutes  (DMs)
        encountered by  a  DS1  interface  in the current
        15 minute interval. noSuchInstance will be
        returned if no data is available."
    ::= { dsx1CurrentEntry 10 }

dsx1CurrentLCVs OBJECT-TYPE
    SYNTAX Gauge32
    ACCESS read-only
    STATUS mandatory
    DESCRIPTION
        "The number of Line Code Violations (LCVs)
        encountered by a DS1 interface in the current 15
        minute interval. noSuchInstance will be returned
        if no data is available."
    ::= { dsx1CurrentEntry 11 }

dsx1IntervalTable OBJECT-TYPE
    SYNTAX SEQUENCE OF Dsx1IntervalEntry
    ACCESS not-accessible
    STATUS mandatory
    DESCRIPTION
        "The DS1 Interval Table contains various
        statistics collected by each DS1 Interface over
        the previous 24 hours of operation.  The past 24
        hours are broken into 96 completed 15 minute
        intervals."
    ::= { ds1 8 }

dsx1IntervalEntry OBJECT-TYPE
    SYNTAX Dsx1IntervalEntry
    ACCESS not-accessible
    STATUS mandatory
    DESCRIPTION
        "An entry in the DS1 Interval table."
    INDEX { dsx1IntervalIndex, dsx1IntervalNumber }
    ::= { dsx1IntervalTable 1 }

Dsx1IntervalEntry ::= SEQUENCE {
    dsx1IntervalIndex InterfaceIndex,
    dsx1IntervalNumber INTEGER,
    dsx1IntervalESs Gauge32,
    dsx1IntervalSESs Gauge32,
    dsx1IntervalSEFSs Gauge32,
    dsx1IntervalUASs Gauge32,
    dsx1IntervalCSSs Gauge32,
    dsx1IntervalPCVs Gauge32,
    dsx1IntervalLESs Gauge32,
    dsx1IntervalBESs Gauge32,
    dsx1IntervalDMs Gauge32,
    dsx1IntervalLCVs Gauge32,
    dsx1IntervalValidData TruthValue
    }

dsx1IntervalIndex OBJECT-TYPE
    SYNTAX InterfaceIndex
--    Rsyntax Integer32
    ACCESS read-only
    STATUS mandatory
    DESCRIPTION
        "The index value which uniquely identifies  the
        DS1  interface  to which this entry is applicable.
        The interface identified by a  particular value
        of  this  index is the same interface as
        identified by the same value as a dsx1LineIndex
        object instance."
    ::= { dsx1IntervalEntry 1 }

dsx1IntervalNumber OBJECT-TYPE
    SYNTAX INTEGER(1..96)
    ACCESS read-only
    STATUS mandatory
    DESCRIPTION
        "A number between 1 and 96, where 1 is the most
        recently completed 15 minute interval and 96 is
        the 15 minutes interval completed 23 hours and 45
        minutes prior to interval 1."
    ::= { dsx1IntervalEntry 2 }

dsx1IntervalESs OBJECT-TYPE
    SYNTAX Gauge32
    ACCESS read-only
    STATUS mandatory
    DESCRIPTION
        "The number of Errored Seconds encountered by a
        DS1  interface in one of the previous 96,
        individual 15 minute, intervals. In the case where
        the agent is a proxy and valid data is not
        available, return noSuchInstance."
    ::= { dsx1IntervalEntry 3 }

dsx1IntervalSESs OBJECT-TYPE
    SYNTAX Gauge32
    ACCESS read-only
    STATUS mandatory
    DESCRIPTION
        "The number of Severely Errored Seconds
        encountered by a DS1 interface in one of the
        previous 96, individual 15 minute, intervals. In
        the case where the agent is a proxy and valid data
        is not available, return noSuchInstance."
    ::= { dsx1IntervalEntry 4 }

dsx1IntervalSEFSs OBJECT-TYPE
    SYNTAX Gauge32
    ACCESS read-only
    STATUS mandatory
    DESCRIPTION
        "The number of Severely Errored Framing Seconds
        encountered  by  a  DS1 interface in one of the
        previous 96, individual 15 minute, intervals.  In
        the case where the agent is a proxy and valid data
        is not available, return noSuchInstance."
    ::= { dsx1IntervalEntry 5 }

dsx1IntervalUASs OBJECT-TYPE
    SYNTAX Gauge32
    ACCESS read-only
    STATUS mandatory
    DESCRIPTION
        "The number of Unavailable Seconds  encountered by
        a  DS1 interface in one of the previous 96,
        individual 15 minute, intervals. In the case where
        the agent is a proxy and valid data is not
        available, return noSuchInstance.  This object may
        decrease if the occurance of unavailable seconds
        occurs across an inteval boundary."
    ::= { dsx1IntervalEntry 6 }

dsx1IntervalCSSs OBJECT-TYPE
    SYNTAX Gauge32
    ACCESS read-only
    STATUS mandatory
    DESCRIPTION
        "The number of Controlled Slip Seconds
        encountered by a DS1 interface in one of the
        previous 96, individual 15 minute, intervals. In
        the case where the agent is a proxy and valid data
        is not available, return noSuchInstance."
    ::= { dsx1IntervalEntry 7 }

dsx1IntervalPCVs OBJECT-TYPE
    SYNTAX Gauge32
    ACCESS read-only
    STATUS mandatory
    DESCRIPTION
        "The number of Path Coding  Violations
        encountered by a DS1 interface in one of the
        previous 96, individual 15 minute, intervals. In
        the case where the agent is a proxy and valid data
        is not available, return noSuchInstance."
    ::= { dsx1IntervalEntry 8 }

dsx1IntervalLESs OBJECT-TYPE
    SYNTAX Gauge32
    ACCESS read-only
    STATUS mandatory
    DESCRIPTION
        "The number of Line Errored Seconds encountered by
        a  DS1 interface in one of the previous 96,
        individual 15 minute, intervals. In the case where
        the agent is a proxy and valid data is not
        available, return noSuchInstance."
    ::= { dsx1IntervalEntry 9 }

dsx1IntervalBESs OBJECT-TYPE
    SYNTAX Gauge32
    ACCESS read-only
    STATUS mandatory
    DESCRIPTION
        "The number of Bursty  Errored  Seconds  (BESs)
        encountered  by  a  DS1 interface in one of the
        previous 96, individual 15 minute, intervals. In
        the case where the agent is a proxy and valid data
        is not available, return noSuchInstance."
    ::= { dsx1IntervalEntry 10 }

dsx1IntervalDMs OBJECT-TYPE
    SYNTAX Gauge32
    ACCESS read-only
    STATUS mandatory
    DESCRIPTION
        "The number of Degraded Minutes  (DMs)
        encountered by a DS1 interface in one of the
        previous 96, individual 15 minute, intervals. In
        the case where the agent is a proxy and valid data
        is not available, return noSuchInstance."
    ::= { dsx1IntervalEntry 11 }

dsx1IntervalLCVs OBJECT-TYPE
    SYNTAX Gauge32
    ACCESS read-only
    STATUS mandatory
    DESCRIPTION
        "The number of Line Code Violations (LCVs)
        encountered  by a DS1 interface in one of the
        previous 96, individual 15 minute, intervals. In
        the case where the agent is a proxy and valid data
        is not available, return noSuchInstance."
    ::= { dsx1IntervalEntry 12 }

dsx1IntervalValidData OBJECT-TYPE
    SYNTAX TruthValue
--    Rsyntax INTEGER {
--        true(1),
--        false(2)
--        }
    ACCESS read-only
    STATUS mandatory
    DESCRIPTION
        "This variable indicates if there is valid data
        for this interval."
    ::= { dsx1IntervalEntry 13 }

dsx1TotalTable OBJECT-TYPE
    SYNTAX SEQUENCE OF Dsx1TotalEntry
    ACCESS not-accessible
    STATUS mandatory
    DESCRIPTION
        "The DS1 Total Table contains the cumulative sum
        of the various statistics for the 24 hour period
        preceding the current interval."
    ::= { ds1 9 }

dsx1TotalEntry OBJECT-TYPE
    SYNTAX Dsx1TotalEntry
    ACCESS not-accessible
    STATUS mandatory
    DESCRIPTION
        "An entry in the DS1 Total table."
    INDEX { dsx1TotalIndex }
    ::= { dsx1TotalTable 1 }

Dsx1TotalEntry ::= SEQUENCE {
    dsx1TotalIndex InterfaceIndex,
    dsx1TotalESs Gauge32,
    dsx1TotalSESs Gauge32,
    dsx1TotalSEFSs Gauge32,
    dsx1TotalUASs Gauge32,
    dsx1TotalCSSs Gauge32,
    dsx1TotalPCVs Gauge32,
    dsx1TotalLESs Gauge32,
    dsx1TotalBESs Gauge32,
    dsx1TotalDMs Gauge32,
    dsx1TotalLCVs Gauge32
    }

dsx1TotalIndex OBJECT-TYPE
    SYNTAX InterfaceIndex
--    Rsyntax Integer32
    ACCESS read-only
    STATUS mandatory
    DESCRIPTION
        "The index value which uniquely identifies  the
        DS1  interface  to which this entry is applicable.
        The interface identified by a  particular value
        of  this  index is the same interface as
        identified by the same value as a dsx1LineIndex
        object instance."
    ::= { dsx1TotalEntry 1 }

dsx1TotalESs OBJECT-TYPE
    SYNTAX Gauge32
    ACCESS read-only
    STATUS mandatory
    DESCRIPTION
        "The sum of Errored Seconds encountered by a DS1
        interface in the previous 24 hour interval.
        Invalid 15 minute intervals count as 0."
    ::= { dsx1TotalEntry 2 }

dsx1TotalSESs OBJECT-TYPE
    SYNTAX Gauge32
    ACCESS read-only
    STATUS mandatory
    DESCRIPTION
        "The number of Severely Errored Seconds
        encountered by  a  DS1  interface in the previous
        24 hour interval.  Invalid 15 minute intervals
        count as 0."
    ::= { dsx1TotalEntry 3 }

dsx1TotalSEFSs OBJECT-TYPE
    SYNTAX Gauge32
    ACCESS read-only
    STATUS mandatory
    DESCRIPTION
        "The number of Severely Errored Framing Seconds
        encountered  by a DS1 interface in the previous 24
        hour interval.  Invalid 15 minute intervals count
        as 0."
    ::= { dsx1TotalEntry 4 }

dsx1TotalUASs OBJECT-TYPE
    SYNTAX Gauge32
    ACCESS read-only
    STATUS mandatory
    DESCRIPTION
        "The number of Unavailable Seconds  encountered by
        a DS1 interface in the previous 24 hour interval.
        Invalid 15 minute intervals count as 0."
    ::= { dsx1TotalEntry 5 }

dsx1TotalCSSs OBJECT-TYPE
    SYNTAX Gauge32
    ACCESS read-only
    STATUS mandatory
    DESCRIPTION
        "The number of Controlled Slip Seconds
        encountered by  a  DS1  interface in the previous
        24 hour interval.  Invalid 15 minute intervals
        count as 0."
    ::= { dsx1TotalEntry 6 }

dsx1TotalPCVs OBJECT-TYPE
    SYNTAX Gauge32
    ACCESS read-only
    STATUS mandatory
    DESCRIPTION
        "The number of Path Coding  Violations
        encountered by  a  DS1  interface in the previous
        24 hour interval.  Invalid 15 minute intervals
        count as 0."
    ::= { dsx1TotalEntry 7 }

dsx1TotalLESs OBJECT-TYPE
    SYNTAX Gauge32
    ACCESS read-only
    STATUS mandatory
    DESCRIPTION
        "The number of Line Errored Seconds encountered by
        a DS1 interface in the previous 24 hour interval.
        Invalid 15 minute intervals count as 0."
    ::= { dsx1TotalEntry 8 }

dsx1TotalBESs OBJECT-TYPE
    SYNTAX Gauge32
    ACCESS read-only
    STATUS mandatory
    DESCRIPTION
        "The number of Bursty  Errored  Seconds  (BESs)
        encountered  by a DS1 interface in the previous 24
        hour interval.  Invalid 15 minute intervals count
        as 0."
    ::= { dsx1TotalEntry 9 }

dsx1TotalDMs OBJECT-TYPE
    SYNTAX Gauge32
    ACCESS read-only
    STATUS mandatory
    DESCRIPTION
        "The number of Degraded Minutes  (DMs)
        encountered by  a  DS1  interface in the previous
        24 hour interval.  Invalid 15 minute intervals
        count as 0."
    ::= { dsx1TotalEntry 10 }

dsx1TotalLCVs OBJECT-TYPE
    SYNTAX Gauge32
    ACCESS read-only
    STATUS mandatory
    DESCRIPTION
        "The number of Line Code Violations (LCVs)
        encountered by a DS1 interface in the current 15
        minute interval.  Invalid 15 minute intervals
        count as 0."
    ::= { dsx1TotalEntry 11 }

dsx1FarEndCurrentTable OBJECT-TYPE
    SYNTAX SEQUENCE OF Dsx1FarEndCurrentEntry
    ACCESS not-accessible
    STATUS mandatory
    DESCRIPTION
        "The DS1 Far End Current table contains various
        statistics being collected for the current 15
        minute interval.  The statistics are collected
        from the far end messages on the Facilities Data
        Link.  The definitions are the same as described
        for the near-end information."
    ::= { ds1 10 }

dsx1FarEndCurrentEntry OBJECT-TYPE
    SYNTAX Dsx1FarEndCurrentEntry
    ACCESS not-accessible
    STATUS mandatory
    DESCRIPTION
        "An entry in the DS1 Far End Current table."
    INDEX { dsx1FarEndCurrentIndex }
    ::= { dsx1FarEndCurrentTable 1 }

Dsx1FarEndCurrentEntry ::= SEQUENCE {
    dsx1FarEndCurrentIndex InterfaceIndex,
    dsx1FarEndTimeElapsed INTEGER,
    dsx1FarEndValidIntervals INTEGER,
    dsx1FarEndCurrentESs Gauge32,
    dsx1FarEndCurrentSESs Gauge32,
    dsx1FarEndCurrentSEFSs Gauge32,
    dsx1FarEndCurrentUASs Gauge32,
    dsx1FarEndCurrentCSSs Gauge32,
    dsx1FarEndCurrentLESs Gauge32,
    dsx1FarEndCurrentPCVs Gauge32,
    dsx1FarEndCurrentBESs Gauge32,
    dsx1FarEndCurrentDMs Gauge32,
    dsx1FarEndInvalidIntervals INTEGER
    }

dsx1FarEndCurrentIndex OBJECT-TYPE
    SYNTAX InterfaceIndex
--    Rsyntax Integer32
    ACCESS read-only
    STATUS mandatory
    DESCRIPTION
        "The index value which uniquely identifies  the
        DS1  interface  to which this entry is applicable.
        The interface identified by a  particular value
        of  this  index is the same interface as
        identified by the same value  an  dsx1LineIndex
        object instance."
    ::= { dsx1FarEndCurrentEntry 1 }

dsx1FarEndTimeElapsed OBJECT-TYPE
    SYNTAX INTEGER(0..899)
    ACCESS read-only
    STATUS mandatory
    DESCRIPTION
        "The number of seconds that  have  elapsed since
        the beginning of the far end current error-
        measurement period."
    ::= { dsx1FarEndCurrentEntry 2 }

dsx1FarEndValidIntervals OBJECT-TYPE
    SYNTAX INTEGER(0..96)
    ACCESS read-only
    STATUS mandatory
    DESCRIPTION
        "The number of previous far end  intervals for
        which  valid data was collected.  The value will
        be 96 unless the interface  was brought  online
        within the last 24 hours, in which case the value
        will be the number of  complete  15  minute far
        end intervals since the interface has been
        online."
    ::= { dsx1FarEndCurrentEntry 3 }

dsx1FarEndCurrentESs OBJECT-TYPE
    SYNTAX Gauge32
    ACCESS read-only
    STATUS mandatory
    DESCRIPTION
        "The number of Far Far End Errored Seconds
        encountered by a DS1 interface in the current 15
        minute interval. noSuchInstance will be returned
        if no data is available."
    ::= { dsx1FarEndCurrentEntry 4 }

dsx1FarEndCurrentSESs OBJECT-TYPE
    SYNTAX Gauge32
    ACCESS read-only
    STATUS mandatory
    DESCRIPTION
        "The number of Far End Severely Errored Seconds
        encountered  by  a DS1 interface in the current 15
        minute interval. noSuchInstance will be returned
        if no data is available."
    ::= { dsx1FarEndCurrentEntry 5 }

dsx1FarEndCurrentSEFSs OBJECT-TYPE
    SYNTAX Gauge32
    ACCESS read-only
    STATUS mandatory
    DESCRIPTION
        "The number of Far End Severely Errored Framing
        Seconds  encountered  by a DS1 interface in the
        current 15 minute interval. noSuchInstance will be
        returned if no data is available."
    ::= { dsx1FarEndCurrentEntry 6 }

dsx1FarEndCurrentUASs OBJECT-TYPE
    SYNTAX Gauge32
    ACCESS read-only
    STATUS mandatory
    DESCRIPTION
        "The number of Unavailable Seconds  encountered by
        a DS1 interface in the current 15 minute interval.
        noSuchInstance will be returned if no data is
        available."
    ::= { dsx1FarEndCurrentEntry 7 }

dsx1FarEndCurrentCSSs OBJECT-TYPE
    SYNTAX Gauge32
    ACCESS read-only
    STATUS mandatory
    DESCRIPTION
        "The number of Far End Controlled Slip  Seconds
        encountered  by  a DS1 interface in the current 15
        minute interval. noSuchInstance will be returned
        if no data is available."
    ::= { dsx1FarEndCurrentEntry 8 }

dsx1FarEndCurrentLESs OBJECT-TYPE
    SYNTAX Gauge32
    ACCESS read-only
    STATUS mandatory
    DESCRIPTION
        "The number of Far End Line Errored Seconds
        encountered by a DS1 interface in the current 15
        minute interval. noSuchInstance will be returned
        if no data is available."
    ::= { dsx1FarEndCurrentEntry 9 }

dsx1FarEndCurrentPCVs OBJECT-TYPE
    SYNTAX Gauge32
    ACCESS read-only
    STATUS mandatory
    DESCRIPTION
        "The number of Far End Path  Coding  Violations
        reported  via the far end block error count
        encountered by a DS1 interface in the current  15
        minute interval. noSuchInstance will be returned
        if no data is available."
    ::= { dsx1FarEndCurrentEntry 10 }

dsx1FarEndCurrentBESs OBJECT-TYPE
    SYNTAX Gauge32
    ACCESS read-only
    STATUS mandatory
    DESCRIPTION
        "The number of Bursty  Errored  Seconds  (BESs)
        encountered  by  a DS1 interface in the current 15
        minute interval. noSuchInstance will be returned
        if no data is available."
    ::= { dsx1FarEndCurrentEntry 11 }

dsx1FarEndCurrentDMs OBJECT-TYPE
    SYNTAX Gauge32
    ACCESS read-only
    STATUS mandatory
    DESCRIPTION
        "The number of Degraded Minutes  (DMs)
        encountered by  a  DS1  interface  in the current
        15 minute interval. noSuchInstance will be
        returned if no data is available."
    ::= { dsx1FarEndCurrentEntry 12 }

dsx1FarEndInvalidIntervals OBJECT-TYPE
    SYNTAX INTEGER(0..96)
    ACCESS read-only
    STATUS mandatory
    DESCRIPTION
        "The number of intervals for which no valid data
        is available."
    ::= { dsx1FarEndCurrentEntry 13 }

dsx1FarEndIntervalTable OBJECT-TYPE
    SYNTAX SEQUENCE OF Dsx1FarEndIntervalEntry
    ACCESS not-accessible
    STATUS mandatory
    DESCRIPTION
        "The DS1 Far End Interval Table contains various
        statistics collected by each DS1 interface over
        the previous 24 hours of operation.  The past 24
        hours are broken into 96 completed 15 minute
        intervals."
    ::= { ds1 11 }

dsx1FarEndIntervalEntry OBJECT-TYPE
    SYNTAX Dsx1FarEndIntervalEntry
    ACCESS not-accessible
    STATUS mandatory
    DESCRIPTION
        "An entry in the DS1 Far End Interval table."
    INDEX { dsx1FarEndIntervalIndex, dsx1FarEndIntervalNumber }
    ::= { dsx1FarEndIntervalTable 1 }

Dsx1FarEndIntervalEntry ::= SEQUENCE {
    dsx1FarEndIntervalIndex InterfaceIndex,
    dsx1FarEndIntervalNumber INTEGER,
    dsx1FarEndIntervalESs Gauge32,
    dsx1FarEndIntervalSESs Gauge32,
    dsx1FarEndIntervalSEFSs Gauge32,
    dsx1FarEndIntervalUASs Gauge32,
    dsx1FarEndIntervalCSSs Gauge32,
    dsx1FarEndIntervalLESs Gauge32,
    dsx1FarEndIntervalPCVs Gauge32,
    dsx1FarEndIntervalBESs Gauge32,
    dsx1FarEndIntervalDMs Gauge32
    }

dsx1FarEndIntervalIndex OBJECT-TYPE
    SYNTAX InterfaceIndex
--    Rsyntax Integer32
    ACCESS read-only
    STATUS mandatory
    DESCRIPTION
        "The index value which uniquely identifies  the
        DS1  interface  to which this entry is applicable.
        The interface identified by a  particular value
        of  this  index is the same interface as
        identified by the same value as a dsx1LineIndex
        object instance."
    ::= { dsx1FarEndIntervalEntry 1 }

dsx1FarEndIntervalNumber OBJECT-TYPE
    SYNTAX INTEGER(1..96)
    ACCESS read-only
    STATUS mandatory
    DESCRIPTION
        "A number between 1 and 96, where 1 is the most
        recently completed 15 minute interval and 96 is
        the 15 minutes interval completed 23 hours and 45
        minutes prior to interval 1."
    ::= { dsx1FarEndIntervalEntry 2 }

dsx1FarEndIntervalESs OBJECT-TYPE
    SYNTAX Gauge32
    ACCESS read-only
    STATUS mandatory
    DESCRIPTION
        "The number of Far End Errored Seconds
        encountered by a DS1 interface in one of the
        previous 96, individual 15 minute, intervals. In
        the case where the agent is a proxy and valid data
        is not available, return noSuchInstance."
    ::= { dsx1FarEndIntervalEntry 3 }

dsx1FarEndIntervalSESs OBJECT-TYPE
    SYNTAX Gauge32
    ACCESS read-only
    STATUS mandatory
    DESCRIPTION
        "The number of Far End Severely Errored Seconds
        encountered  by  a  DS1 interface in one of the
        previous 96, individual 15 minute, intervals. In
        the case where the agent is a proxy and valid data
        is not available, return noSuchInstance."
    ::= { dsx1FarEndIntervalEntry 4 }

dsx1FarEndIntervalSEFSs OBJECT-TYPE
    SYNTAX Gauge32
    ACCESS read-only
    STATUS mandatory
    DESCRIPTION
        "The number of Far End Severely Errored Framing
        Seconds  encountered  by a DS1 interface in one of
        the previous 96, individual 15  minute,
        intervals.  In the case where the agent is a proxy
        and valid data is not available, return
        noSuchInstance."
    ::= { dsx1FarEndIntervalEntry 5 }

dsx1FarEndIntervalUASs OBJECT-TYPE
    SYNTAX Gauge32
    ACCESS read-only
    STATUS mandatory
    DESCRIPTION
        "The number of Unavailable Seconds  encountered by
        a  DS1 interface in one of the previous 96,
        individual 15 minute, intervals. In the case where
        the agent is a proxy and valid data is not
        available, return noSuchInstance."
    ::= { dsx1FarEndIntervalEntry 6 }

dsx1FarEndIntervalCSSs OBJECT-TYPE
    SYNTAX Gauge32
    ACCESS read-only
    STATUS mandatory
    DESCRIPTION
        "The number of Far End Controlled Slip  Seconds
        encountered  by  a  DS1 interface in one of the
        previous 96, individual 15 minute, intervals. In
        the case where the agent is a proxy and valid data
        is not available, return noSuchInstance."
    ::= { dsx1FarEndIntervalEntry 7 }

dsx1FarEndIntervalLESs OBJECT-TYPE
    SYNTAX Gauge32
    ACCESS read-only
    STATUS mandatory
    DESCRIPTION
        "The number of Far End Line Errored Seconds
        encountered by a DS1 interface in one of the
        previous 96, individual 15 minute, intervals. In
        the case where the agent is a proxy and valid data
        is not available, return noSuchInstance."
    ::= { dsx1FarEndIntervalEntry 8 }

dsx1FarEndIntervalPCVs OBJECT-TYPE
    SYNTAX Gauge32
    ACCESS read-only
    STATUS mandatory
    DESCRIPTION
        "The number of Far End Path  Coding  Violations
        reported  via the far end block error count
        encountered by a DS1 interface in one of the
        previous 96, individual 15 minute, intervals. In
        the case where the agent is a proxy and valid data
        is not available, return noSuchInstance."
    ::= { dsx1FarEndIntervalEntry 9 }

dsx1FarEndIntervalBESs OBJECT-TYPE
    SYNTAX Gauge32
    ACCESS read-only
    STATUS mandatory
    DESCRIPTION
        "The number of Bursty  Errored  Seconds  (BESs)
        encountered  by  a  DS1 interface in one of the
        previous 96, individual 15 minute, intervals. In
        the case where the agent is a proxy and valid data
        is not available, return noSuchInstance."
    ::= { dsx1FarEndIntervalEntry 10 }

dsx1FarEndIntervalDMs OBJECT-TYPE
    SYNTAX Gauge32
    ACCESS read-only
    STATUS mandatory
    DESCRIPTION
        "The number of Degraded Minutes  (DMs)
        encountered by a DS1 interface in one of the
        previous 96, individual 15 minute, intervals. In
        the case where the agent is a proxy and valid data
        is not available, return noSuchInstance."
    ::= { dsx1FarEndIntervalEntry 11 }

dsx1FarEndTotalTable OBJECT-TYPE
    SYNTAX SEQUENCE OF Dsx1FarEndTotalEntry
    ACCESS not-accessible
    STATUS mandatory
    DESCRIPTION
        "The DS1 Far End Total Table contains the
        cumulative sum of the various statistics for the
        24 hour period preceding the current interval."
    ::= { ds1 12 }

dsx1FarEndTotalEntry OBJECT-TYPE
    SYNTAX Dsx1FarEndTotalEntry
    ACCESS not-accessible
    STATUS mandatory
    DESCRIPTION
        "An entry in the DS1 Far End Total table."
    INDEX { dsx1FarEndTotalIndex }
    ::= { dsx1FarEndTotalTable 1 }

Dsx1FarEndTotalEntry ::= SEQUENCE {
    dsx1FarEndTotalIndex InterfaceIndex,
    dsx1FarEndTotalESs Gauge32,
    dsx1FarEndTotalSESs Gauge32,
    dsx1FarEndTotalSEFSs Gauge32,
    dsx1FarEndTotalUASs Gauge32,
    dsx1FarEndTotalCSSs Gauge32,
    dsx1FarEndTotalLESs Gauge32,
    dsx1FarEndTotalPCVs Gauge32,
    dsx1FarEndTotalBESs Gauge32,
    dsx1FarEndTotalDMs Gauge32
    }

dsx1FarEndTotalIndex OBJECT-TYPE
    SYNTAX InterfaceIndex
--    Rsyntax Integer32
    ACCESS read-only
    STATUS mandatory
    DESCRIPTION
        "The index value which uniquely identifies  the
        DS1  interface  to which this entry is applicable.
        The interface identified by a  particular value
        of  this  index is the same interface as
        identified by the same value  an  dsx1LineIndex
        object instance."
    ::= { dsx1FarEndTotalEntry 1 }

dsx1FarEndTotalESs OBJECT-TYPE
    SYNTAX Gauge32
    ACCESS read-only
    STATUS mandatory
    DESCRIPTION
        "The number of Far End Errored Seconds
        encountered by  a  DS1  interface in the previous
        24 hour interval.  Invalid 15 minute intervals
        count as 0."
    ::= { dsx1FarEndTotalEntry 2 }

dsx1FarEndTotalSESs OBJECT-TYPE
    SYNTAX Gauge32
    ACCESS read-only
    STATUS mandatory
    DESCRIPTION
        "The number of Far End Severely Errored Seconds
        encountered  by a DS1 interface in the previous 24
        hour interval.  Invalid 15 minute intervals count
        as 0."
    ::= { dsx1FarEndTotalEntry 3 }

dsx1FarEndTotalSEFSs OBJECT-TYPE
    SYNTAX Gauge32
    ACCESS read-only
    STATUS mandatory
    DESCRIPTION
        "The number of Far End Severely Errored Framing
        Seconds  encountered  by a DS1 interface in the
        previous 24 hour interval.  Invalid 15 minute
        intervals count as 0."
    ::= { dsx1FarEndTotalEntry 4 }

dsx1FarEndTotalUASs OBJECT-TYPE
    SYNTAX Gauge32
    ACCESS read-only
    STATUS mandatory
    DESCRIPTION
        "The number of Unavailable Seconds  encountered by
        a DS1 interface in the previous 24 hour interval.
        Invalid 15 minute intervals count as 0."
    ::= { dsx1FarEndTotalEntry 5 }

dsx1FarEndTotalCSSs OBJECT-TYPE
    SYNTAX Gauge32
    ACCESS read-only
    STATUS mandatory
    DESCRIPTION
        "The number of Far End Controlled Slip  Seconds
        encountered  by a DS1 interface in the previous 24
        hour interval.  Invalid 15 minute intervals count
        as 0."
    ::= { dsx1FarEndTotalEntry 6 }

dsx1FarEndTotalLESs OBJECT-TYPE
    SYNTAX Gauge32
    ACCESS read-only
    STATUS mandatory
    DESCRIPTION
        "The number of Far End Line Errored Seconds
        encountered by a DS1 interface in the previous 24
        hour interval.  Invalid 15 minute intervals count
        as 0."
    ::= { dsx1FarEndTotalEntry 7 }

dsx1FarEndTotalPCVs OBJECT-TYPE
    SYNTAX Gauge32
    ACCESS read-only
    STATUS mandatory
    DESCRIPTION
        "The number of Far End Path  Coding  Violations
        reported  via the far end block error count
        encountered by a DS1 interface in the previous 24
        hour interval.  Invalid 15 minute intervals count
        as 0."
    ::= { dsx1FarEndTotalEntry 8 }

dsx1FarEndTotalBESs OBJECT-TYPE
    SYNTAX Gauge32
    ACCESS read-only
    STATUS mandatory
    DESCRIPTION
        "The number of Bursty  Errored  Seconds  (BESs)
        encountered  by a DS1 interface in the previous 24
        hour interval.  Invalid 15 minute intervals count
        as 0."
    ::= { dsx1FarEndTotalEntry 9 }

dsx1FarEndTotalDMs OBJECT-TYPE
    SYNTAX Gauge32
    ACCESS read-only
    STATUS mandatory
    DESCRIPTION
        "The number of Degraded Minutes  (DMs)
        encountered by  a  DS1  interface in the previous
        24 hour interval.  Invalid 15 minute intervals
        count as 0."
    ::= { dsx1FarEndTotalEntry 10 }

dsx1FracTable OBJECT-TYPE
    SYNTAX SEQUENCE OF Dsx1FracEntry
    ACCESS not-accessible
    STATUS deprecated
    DESCRIPTION
        "This table is deprecated.
        
        It was mandatory for systems dividing a DS1 into
        channels containing different data streams that
        are of local interest.  Systems which are
        indifferent to data content, such as CSUs, need
        not implement it.
        
        The DS1 fractional table identifies which DS1
        channels associated with a CSU are being used to
        support a logical interface, i.e., an entry in the
        interfaces table from the Internet-standard MIB.
        
        For example, consider an application managing a
        North American ISDN Primary Rate link whose
        division is a 384 kbit/s H1 _B_ Channel for Video,
        a second H1 for data to a primary routing peer,
        and 12 64 kbit/s H0 _B_ Channels. Consider that
        some subset of the H0 channels are used for voice
        and the remainder are available for dynamic data
        calls.
        
        We count a total of 14 interfaces multiplexed onto
        the DS1 interface. Six DS1 channels (for the sake
        of the example, channels 1..6) are used for Video,
        six more (7..11 and 13) are used for data, and the
        remaining 12 are are in channels 12 and 14..24.
        
        Let us further imagine that ifIndex 2 is of type
        DS1 and refers to the DS1 interface, and that the
        interfaces layered onto it are numbered 3..16.
        
        We might describe the allocation of channels, in
        the dsx1FracTable, as follows:
        dsx1FracIfIndex.2. 1 = 3  dsx1FracIfIndex.2.13 = 4
        dsx1FracIfIndex.2. 2 = 3  dsx1FracIfIndex.2.14 = 6
        dsx1FracIfIndex.2. 3 = 3  dsx1FracIfIndex.2.15 = 7
        dsx1FracIfIndex.2. 4 = 3  dsx1FracIfIndex.2.16 = 8
        dsx1FracIfIndex.2. 5 = 3  dsx1FracIfIndex.2.17 = 9
        dsx1FracIfIndex.2. 6 = 3  dsx1FracIfIndex.2.18 = 10
        dsx1FracIfIndex.2. 7 = 4  dsx1FracIfIndex.2.19 = 11
        dsx1FracIfIndex.2. 8 = 4  dsx1FracIfIndex.2.20 = 12
        dsx1FracIfIndex.2. 9 = 4  dsx1FracIfIndex.2.21 = 13
        dsx1FracIfIndex.2.10 = 4  dsx1FracIfIndex.2.22 = 14
        dsx1FracIfIndex.2.11 = 4  dsx1FracIfIndex.2.23 = 15
        dsx1FracIfIndex.2.12 = 5  dsx1FracIfIndex.2.24 = 16
        
        For North American (DS1) interfaces, there are 24
        legal channels, numbered 1 through 24.
        
        For G.704 interfaces, there are 31 legal channels,
        numbered 1 through 31.  The channels (1..31)
        correspond directly to the equivalently numbered
        time-slots."
    ::= { ds1 13 }

dsx1FracEntry OBJECT-TYPE
    SYNTAX Dsx1FracEntry
    ACCESS not-accessible
    STATUS deprecated
    DESCRIPTION
        "An entry in the DS1 Fractional table."
    INDEX { dsx1FracIndex, dsx1FracNumber }
    ::= { dsx1FracTable 1 }

Dsx1FracEntry ::= SEQUENCE {
    dsx1FracIndex INTEGER,
    dsx1FracNumber INTEGER,
    dsx1FracIfIndex INTEGER
    }

dsx1FracIndex OBJECT-TYPE
    SYNTAX INTEGER(1..2147483647)
    ACCESS read-only
    STATUS deprecated
    DESCRIPTION
        "The index value which uniquely identifies  the
        DS1  interface  to which this entry is applicable
        The interface identified by a  particular
        value  of  this  index is the same interface as
        identified by the same value  an  dsx1LineIndex
        object instance."
    ::= { dsx1FracEntry 1 }

dsx1FracNumber OBJECT-TYPE
    SYNTAX INTEGER(1..31)
    ACCESS read-only
    STATUS deprecated
    DESCRIPTION
        "The channel number for this entry."
    ::= { dsx1FracEntry 2 }

dsx1FracIfIndex OBJECT-TYPE
    SYNTAX INTEGER(1..2147483647)
    ACCESS read-write
    STATUS deprecated
    DESCRIPTION
        "An index value that uniquely identifies an
        interface.  The interface identified by a particular
        value of this index is the same  interface
        as  identified by the same value an ifIndex
        object instance. If no interface is currently using
        a channel, the value should be zero.  If a
        single interface occupies more  than  one  time
        slot,  that ifIndex value will be found in multiple
        time slots."
    ::= { dsx1FracEntry 3 }

dsx1LineStatusChange TRAP-TYPE
--?? Non-reverse mappable trap
    ENTERPRISE ds1Traps
    VARIABLES {
        dsx1LineStatus, dsx1LineStatusLastChange }
--  Status
--    mandatory
    DESCRIPTION
        "A dsx1LineStatusChange trap is sent when the
        value of an instance dsx1LineStatus changes. It
        can be utilized by an NMS to trigger polls.  When
        the line status change results from a higher level
        line status change (i.e. ds3), then no traps for
        the ds1 are sent."
    ::= 1

ds1NearEndConfigGroup OBJECT IDENTIFIER ::= { ds1Groups 1 }
-- OBJECT-GROUP
--  Status
--    mandatory
--  Descr
--    A collection of objects providing configuration
--    information applicable to all DS1 interfaces.
--  objects
--    dsx1TimeElapsed, dsx1ValidIntervals, dsx1LineType, 
--    dsx1LineCoding, dsx1SendCode, dsx1LoopbackConfig, 
--    dsx1LineStatus, dsx1SignalMode, dsx1TransmitClockSource, 
--    dsx1Fdl, dsx1InvalidIntervals, dsx1LineLength

ds1NearEndCurrentGroup OBJECT IDENTIFIER ::= { ds1Groups 2 }
-- OBJECT-GROUP
--  Status
--    mandatory
--  Descr
--    A collection of objects providing statistics
--    information for the current interval applicable to
--    all DS1 interfaces.
--  objects
--    dsx1CurrentIndex, dsx1CurrentESs, dsx1CurrentSESs, 
--    dsx1CurrentSEFSs, dsx1CurrentUASs, dsx1CurrentCSSs, 
--    dsx1CurrentPCVs, dsx1CurrentLESs, dsx1CurrentBESs, 
--    dsx1CurrentDMs, dsx1CurrentLCVs

ds1NearEndIntervalGroup OBJECT IDENTIFIER ::= { ds1Groups 3 }
-- OBJECT-GROUP
--  Status
--    mandatory
--  Descr
--    A collection of objects providing statistics
--    
--    
--    
--    
--    information for the last 96 intervals applicable
--    to all DS1 interfaces.
--  objects
--    dsx1IntervalIndex, dsx1IntervalNumber, dsx1IntervalESs, 
--    dsx1IntervalSESs, dsx1IntervalSEFSs, dsx1IntervalUASs, 
--    dsx1IntervalCSSs, dsx1IntervalPCVs, dsx1IntervalLESs, 
--    dsx1IntervalBESs, dsx1IntervalDMs, dsx1IntervalLCVs, 
--    dsx1IntervalValidData

ds1NearEndTotalGroup OBJECT IDENTIFIER ::= { ds1Groups 4 }
-- OBJECT-GROUP
--  Status
--    mandatory
--  Descr
--    A collection of objects providing statistics
--    information for the total of the last 96 intervals
--    applicable to all DS1 interfaces.
--  objects
--    dsx1TotalIndex, dsx1TotalESs, dsx1TotalSESs, dsx1TotalSEFSs, 
--    dsx1TotalUASs, dsx1TotalCSSs, dsx1TotalPCVs, dsx1TotalLESs, 
--    dsx1TotalBESs, dsx1TotalDMs, dsx1TotalLCVs

ds1FarEndGroup OBJECT IDENTIFIER ::= { ds1Groups 5 }
-- OBJECT-GROUP
--  Status
--    mandatory
--  Descr
--    A collection of objects providing remote
--    configuration and statistics information.
--  objects
--    dsx1FarEndCurrentIndex, dsx1FarEndTimeElapsed, 
--    dsx1FarEndValidIntervals, dsx1FarEndCurrentESs, 
--    dsx1FarEndCurrentSESs, dsx1FarEndCurrentSEFSs, 
--    dsx1FarEndCurrentUASs, dsx1FarEndCurrentCSSs, 
--    dsx1FarEndCurrentLESs, dsx1FarEndCurrentPCVs, 
--    dsx1FarEndCurrentBESs, dsx1FarEndCurrentDMs, 
--    dsx1FarEndInvalidIntervals, dsx1FarEndIntervalIndex, 
--    dsx1FarEndIntervalNumber, dsx1FarEndIntervalESs, 
--    dsx1FarEndIntervalSESs, dsx1FarEndIntervalSEFSs, 
--    dsx1FarEndIntervalUASs, dsx1FarEndIntervalCSSs, 
--    dsx1FarEndIntervalLESs, dsx1FarEndIntervalPCVs, 
--    dsx1FarEndIntervalBESs, dsx1FarEndIntervalDMs, 
--    dsx1FarEndTotalIndex, dsx1FarEndTotalESs, dsx1FarEndTotalSESs, 
--    dsx1FarEndTotalSEFSs, dsx1FarEndTotalUASs, 
--    dsx1FarEndTotalCSSs, dsx1FarEndTotalLESs, dsx1FarEndTotalPCVs, 
--    dsx1FarEndTotalBESs, dsx1FarEndTotalDMs

ds1DeprecatedGroup OBJECT IDENTIFIER ::= { ds1Groups 6 }
-- OBJECT-GROUP
--  Status
--    deprecated
--  Descr
--    A collection of obsolete objects that may be
--    implemented for backwards compatibility.
--  objects
--    dsx1IfIndex, dsx1CircuitIdentifier, dsx1FracIndex, 
--    dsx1FracNumber, dsx1FracIfIndex

ds1NearEndOptionalConfigGroup OBJECT IDENTIFIER ::= { ds1Groups 7 }
-- OBJECT-GROUP
--  Status
--    mandatory
--  Descr
--    A collection of objects that may be implemented
--    on DS1 and DS2 interfaces.
--  objects
--    dsx1LineStatusLastChange, dsx1LineStatusChangeTrapEnable

ds1DS2Group OBJECT IDENTIFIER ::= { ds1Groups 8 }
-- OBJECT-GROUP
--  Status
--    mandatory
--  Descr
--    A collection of objects providing
--     information about DS2 (6,312 kbps)
--     systems.
--  objects
--    dsx1LineIndex, dsx1LineType, dsx1LineCoding, dsx1SendCode, 
--    dsx1LineStatus, dsx1SignalMode, dsx1TransmitClockSource

ds1TransStatsGroup OBJECT IDENTIFIER ::= { ds1Groups 9 }
-- OBJECT-GROUP
--  Status
--    mandatory
--  Descr
--    A collection of objects which are the
--    statistics which can be collected from a ds1
--    interface that is running transparent or unframed
--    lineType.  Statistics not in this list should
--    return noSuchInstance.
--  objects
--    dsx1CurrentESs, dsx1CurrentSESs, dsx1CurrentUASs, 
--    dsx1IntervalESs, dsx1IntervalSESs, dsx1IntervalUASs, 
--    dsx1TotalESs, dsx1TotalSESs, dsx1TotalUASs

ds1Compliance OBJECT IDENTIFIER ::= { ds1Compliances 1 }
-- MODULE-COMPLIANCE
--  Status
--    mandatory
--  Descr
--    The compliance statement for T1 and E1
--    interfaces.
--  Module
--    >>current<<
--   MandGroup
--    ds1NearEndConfigGroup
--   MandGroup
--    ds1NearEndCurrentGroup
--   MandGroup
--    ds1NearEndIntervalGroup
--   MandGroup
--    ds1NearEndTotalGroup
--   OptGroup
--    ds1FarEndGroup
--   OptGroup
--    ds1NearEndOptionalConfigGroup
--   OptGroup
--    ds1DS2Group
--   OptGroup
--    ds1TransStatsGroup

ds1MibT1PriCompliance OBJECT IDENTIFIER ::= { ds1Compliances 2 }
-- MODULE-COMPLIANCE
--  Status
--    mandatory
--  Descr
--    Compliance statement for using this MIB for ISDN
--    Primary Rate interfaces on T1 lines.
--  Module
--    >>current<<
--   MandGroup
--    ds1NearEndConfigGroup
--   MandGroup
--    ds1NearEndCurrentGroup
--   MandGroup
--    ds1NearEndIntervalGroup
--   MandGroup
--    ds1NearEndTotalGroup
--   ObjVar
--    dsx1LineType
--   ObjVar
--    dsx1LineCoding
--   ObjVar
--    dsx1SignalMode
--   ObjVar
--    dsx1TransmitClockSource
--   ObjVar
--    dsx1Fdl

ds1MibE1PriCompliance OBJECT IDENTIFIER ::= { ds1Compliances 3 }
-- MODULE-COMPLIANCE
--  Status
--    mandatory
--  Descr
--    Compliance statement for using this MIB for ISDN
--    Primary Rate interfaces on E1 lines.
--  Module
--    >>current<<
--   MandGroup
--    ds1NearEndConfigGroup
--   MandGroup
--    ds1NearEndCurrentGroup
--   MandGroup
--    ds1NearEndIntervalGroup
--   MandGroup
--    ds1NearEndTotalGroup
--   ObjVar
--    dsx1LineType
--   ObjVar
--    dsx1LineCoding
--   ObjVar
--    dsx1SignalMode
--   ObjVar
--    dsx1TransmitClockSource
--   ObjVar
--    dsx1Fdl


END
