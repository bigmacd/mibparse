SNMP-COMMUNITY-MIB DEFINITIONS ::= BEGIN

   IMPORTS
       MODULE-IDENTITY,
       OBJECT-TYPE,
       Integer32,
       Counter32,
       UInteger32
           FROM SNMPv2-SMI
       RowStatus,
       TestAndIncr,
       StorageType
           FROM SNMPv2-TC
       SnmpAdminString
           FROM SNMP-FRAMEWORK-MIB
       SnmpTagValue
           FROM SNMP-TARGET-MIB
       MODULE-COMPLIANCE,
       OBJECT-GROUP
           FROM SNMPv2-CONF;

   snmpCommunityMIB MODULE-IDENTITY
       LAST-UPDATED "9805110000Z"            -- 11 May 1998, midnight
       ORGANIZATION "SNMPv3 Working Group"
       CONTACT-INFO "WG-email:   snmpv3@tis.com
                     Subscribe:  majordomo@tis.com
                                 In msg body:  subscribe snmpv3

                     Chair:      Russ Mundy
                                 Trusted Information Systems
                     postal:     3060 Washington Rd
                                 Glenwood MD 21738
                                 USA
                     email:      mundy@tis.com
                     phone:      +1-301-854-6889

                     Co-editor:  Rob Frye
                                 MCI Communications Corp.
                     Postal:     2100 Reston Parkway, Suite 600
                                 Reston, VA 20191
                                 USA
                     E-mail:     Rob.Frye@mci.com
                     Phone:      +1 703 715 7225

                     Co-editor:  David B. Levi
                                 SNMP Research, Inc.
                     Postal:     3001 Kimberlin Heights Road
                                 Knoxville, TN 37920-9716
                     E-mail:     levi@snmp.com
                     Phone:      +1 423 573 1434

                     Co-editor:  Bert Wijnen
                                 IBM T. J. Watson Research
                     postal:     Schagen 33
                                 3461 GL Linschoten
                                 Netherlands
                     email:      wijnen@vnet.ibm.com
                     phone:      +31-348-432-794
                    "

           DESCRIPTION
               "This MIB module defines objects to help support coexistence
                between SNMPv1, SNMPv2, and SNMPv3."
       ::= { snmpModules xxx }   -- get assignment from IANA

   -- Administrative assignments ****************************************

   snmpCommunityMIBObjects     OBJECT IDENTIFIER ::= { snmpCommunityMIB 1 }
   snmpCommunityMIBConformance OBJECT IDENTIFIER ::= { snmpCommunityMIB 2 }

   --
   -- The snmpCommunityTable contains a database of community strings.
   -- This table provides mappings between community strings, and the
   -- parameters required for View-based Access Control.
   --

   snmpCommunityTable OBJECT-TYPE
       SYNTAX       SEQUENCE OF SnmpCommunityEntry
       MAX-ACCESS   not-accessible
       STATUS       current
       DESCRIPTION
           "The table of community strings configured in the SNMP
            engine's Local Configuration Datastore (LCD)."
       ::= { snmpCommunityMIBObjects 1 }

   snmpCommunityEntry OBJECT-TYPE
       SYNTAX       SnmpCommunityEntry
       MAX-ACCESS   not-accessible
       STATUS       current
       DESCRIPTION
           "Information about a particular community string."
       INDEX       { snmpCommunityIndex }
       ::= { snmpCommunityTable 1 }

   SnmpCommunityEntry ::= SEQUENCE {
       snmpCommunityIndex               Integer32,
       snmpCommunityName                OCTET STRING,
       snmpCommunitySecurityName        SnmpAdminString,
       snmpCommunityContextEngineID     SnmpEngineID,
       snmpCommunityContextName         SnmpAdminString,
       snmpCommunityTransportTag        SnmpTagValue,
       snmpCommunityStorageType         StorageType,
       snmpCommunityStatus              RowStatus
   }

   snmpCommunityIndex OBJECT-TYPE
       SYNTAX      Integer32
       MAX-ACCESS  not-accessible
       STATUS      current
       DESCRIPTION
           "The unique index value of a row in this table."
       ::= { snmpCommunityEntry 1 }

   snmpCommunityName OBJECT-TYPE
       SYNTAX       OCTET STRING (SIZE(1..64))
       MAX-ACCESS   read-create
       STATUS       current
       DESCRIPTION
           "The community string for which a row in this table
            represents a configuration."
       ::= { snmpCommunityEntry 2 }

   snmpCommunitySecurityName OBJECT-TYPE
       SYNTAX       SnmpAdminString
       MAX-ACCESS   read-create
       STATUS       current
       DESCRIPTION
           "A human readable string representing the corresponding
            value of snmpCommunityName in a Security Model
            independent format."
       ::= { snmpCommunityEntry 3 }

   snmpCommunityContextEngineID OBJECT-TYPE
       SYNTAX       SnmpEngineID
       MAX-ACCESS   read-create
       STATUS       current
       DESCRIPTION
           "The contextEngineID indicating the location of the
            context in which management information is accessed
            when using the community string specified by the
            corresponding instance of snmpCommunityName.

            The default value is the snmpEngineID of the entity in
            which this object is instantiated."
       ::= { snmpCommunityEntry 4 }

   snmpCommunityContextName OBJECT-TYPE
       SYNTAX       SnmpAdminString
       MAX-ACCESS   read-create
       STATUS       current
       DESCRIPTION
           "The context in which management information is accessed
            when using the community string specified by the corresponding
            instance of snmpCommunityName."
       DEFVAL      { ''H }   -- the empty string
       ::= { snmpCommunityEntry 5 }

   -- Comments on TransportTag
   --    based on this tag we can limit the use of an entry to a defined
   --    set of transport end-points. Maybe we want to augemnt the
   --    snmpTargetAddrTable to also contain a snmpTargetAddrTMask
   --    of type TAddress which we can use as a mask.
   --    Opinions are welcome.

   snmpCommunityTransportTag OBJECT-TYPE
       SYNTAX       SnmpTagValue
       MAX-ACCESS   read-create
       STATUS       current
       DESCRIPTION
           "This object specifies a set of transport endpoints
            from which an agent will accept management requests.
            If a management request containing this community
            is received on a transport endpoint other than the
            transport endpoints identified by this object, the
            request is deemed unauthentic.

            The transports identified by this object are specified
            in the snmpTargteAddrTable.  Entries in that table
            whose snmpTargetAddrTagList contains this tag value
            are identified.

            If the value of this object has zero-length, transport
            endpoints are not checked when authenticating messages
            containing this community string."
       DEFVAL      { ''H }   -- the empty string
       ::= { snmpCommunityEntry 6 }

   snmpCommunityStorageType OBJECT-TYPE
       SYNTAX       StorageType
       MAX-ACCESS   read-create
       STATUS       current
       DESCRIPTION
           "The storage type for this conceptual row in the
            snmpCommunityTable.  Conceptual rows having the value
            'permanent' need not allow write-access to any
            columnar object in the row."
       ::= { snmpCommunityEntry 7 }

   snmpCommunityStatus OBJECT-TYPE
       SYNTAX       RowStatus
       MAX-ACCESS   read-create
       STATUS       current
       DESCRIPTION
           "The status of this conceptual row in the snmpCommunityTable.

            An entry in this table is not qualified for activation
            until instances of all corresponding columns have been
            initialized, either through default values, or through
            Set operations.  The snmpCommunityName and
            snmpCommunitySecurityName objects must be explicitly set."
       ::= { snmpCommunityEntry 8 }

   -- Conformance Information *******************************************

   snmpCommunityMIBCompliances OBJECT IDENTIFIER
                               ::= { snmpCommunityMIBConformance 1 }
   snmpCommunityMIBGroups      OBJECT IDENTIFIER
                               ::= { snmpCommunityMIBConformance 2 }

   -- Compliance statements

   snmpCommunityMIBCompliance MODULE-COMPLIANCE
       STATUS       current
       DESCRIPTION
           "The compliance statement for SNMP engines which
            implement the SNMP-COMMUNITY-MIB."

       MODULE       -- this module
           MANDATORY-GROUPS { snmpCommunityGroup }

           OBJECT           snmpCommunityName
           MIN-ACCESS       read-only
           DESCRIPTION     "Write access is not required."

           OBJECT           snmpCommunitySecurityName
           MIN-ACCESS       read-only
           DESCRIPTION     "Write access is not required."

           OBJECT           snmpCommunitySecurityLevel
           MIN-ACCESS       read-only
           DESCRIPTION     "Write access is not required."

           OBJECT           snmpCommunityContextEngineID
           MIN-ACCESS       read-only
           DESCRIPTION     "Write access is not required."

           OBJECT           snmpCommunityContextName
           MIN-ACCESS       read-only
           DESCRIPTION     "Write access is not required."

           OBJECT           snmpCommunityTransportLabel
           MIN-ACCESS       read-only
           DESCRIPTION     "Write access is not required."

           OBJECT           snmpCommunityStorageType
           MIN-ACCESS       read-only
           DESCRIPTION     "Write access is not required."

           OBJECT           snmpCommunityStatus
           MIN-ACCESS       read-only
           DESCRIPTION     "Write access is not required."

       ::= { usmMIBCompliances 1 }

   snmpCommunityGroup OBJECT-GROUP
       OBJECTS {
           snmpCommunityIndex,
           snmpCommunityName,
           snmpCommunitySecurityName,
           snmpCommunityContextEngineID,
           snmpCommunityContextName,
           snmpCommunityTransportLabel,
           snmpCommunityStorageType,
           snmpCommunityStatus
       }
       STATUS       current
       DESCRIPTION
           "A collection of objects providing for configuration
            of community strings for SNMPv1 or SNMPv2c usage."
       ::= { snmpCommunityMIBGroups 1 }

   END
