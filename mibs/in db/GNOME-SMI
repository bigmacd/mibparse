GNOME-SMI DEFINITIONS ::= BEGIN

IMPORTS
	MODULE-IDENTITY,
	OBJECT-IDENTITY,
	enterprises
		FROM SNMPv2-SMI;

gnome MODULE-IDENTITY
	LAST-UPDATED "9809010000Z"
	ORGANIZATION "GNOME project"
	CONTACT-INFO
		"GNU Network Object Model Environment project
		
		see http://www.gnome.org for contact persons of a particular
		area or subproject of GNOME.

		Administrative contact for MIB module:

		Jochen Friedrich
		Wingertstr. 70/1
		68809 Neulußheim
		Germany 

		email: snmp@gnome.org"
	DESCRIPTION
		"The Structure of GNOME."
	::= { enterprises 3317 }	-- assigned by IANA

gnomeProducts OBJECT-IDENTITY
	STATUS	current
	DESCRIPTION
		"gnomeProducts is the root OBJECT IDENTIFIER from
		which sysObjectID values are assigned.  Actual
		values are defined in GNOME-PRODUCTS-MIB."
	::= { gnome 1 }                 -- GNOME-PRODUCTS-MIB

gxsnmp OBJECT-IDENTITY
	STATUS  current
	DESCRIPTION
		"gxsnmp is a basic SNMP management application that allows
		you to better manage your network.  Actual values
		are defined in GNOME-GXSNMP-MIB."
	::= { gnome 2 }                 -- GNOME-GXSNMP-MIB

END
