--
--
-- Copyright (c) 1991 by
-- Cascade Communications Corporation, Westford, Mass.
-- All rights reserved.
--
-- This software is the property of Cascade Communications Corp. 
-- This software or any other copies thereof may not be provided or
-- otherwise made available to any other person outside Cascade 
-- Communications Corp. 
--
-- MODULE NAME
--
--	protconn.mib
--
-- COMPONENT
--
--	cascade MIB
--
-- ABSTRACT
--
--	This is a MIB definition for the protocol connections
--	address table. It identifies addresses on interfaces
--	where layer 3 (protocol) processing will occur.
--
--

CASCADE-PROTCONNECT-MIB DEFINITIONS ::= BEGIN

IMPORTS
        OBJECT-TYPE
                FROM RFC-1212
        protconnect, Index
                FROM CASCADE-MIB;

protconnectTable OBJECT-TYPE
	SYNTAX SEQUENCE OF ProtconnectEntry
	ACCESS not-accessible
	STATUS mandatory
	DESCRIPTION
		"A list of physical addresses which will terminate protocols."
	::= { protconnect 1 }

protconnectEntry OBJECT-TYPE
	SYNTAX ProtconnectEntry
	ACCESS not-accessible
	STATUS mandatory
	DESCRIPTION
		"The Protocol Connection Entry."
	INDEX { protconnectIface, protconnectAddress }
	::= { protconnectTable 1 }

ProtconnectEntry ::= SEQUENCE {
	protconnectIface
		Index,
	protconnectAddress
		OCTET STRING,
	protconnectStatus
		INTEGER,
	protconnectState
		INTEGER
	}

protconnectIface OBJECT-TYPE
	SYNTAX Index
	ACCESS read-write
	STATUS mandatory
	DESCRIPTION
		"The interface as defined by MIB-II where the layer 2
		 address is assigned."
	::= { protconnectEntry 1}

protconnectAddress OBJECT-TYPE
	SYNTAX OCTET STRING
	ACCESS read-write
	STATUS mandatory
	DESCRIPTION
		"The layer 2 address assigned to this protocol connection.
		 Length may be implementation limited to 8 octets and is
		 little endian byte ordered. The interpratation of this
		 octet string will depend on the type of interface."
	::= { protconnectEntry 2 }

protconnectStatus OBJECT-TYPE
	SYNTAX INTEGER {
		valid(1),
		invalid(2)
	}
	ACCESS read-write
	STATUS mandatory
	DESCRIPTION
		"A control row to delete the entry."
	::= { protconnectEntry 3 }

protconnectState OBJECT-TYPE
	SYNTAX INTEGER
	ACCESS read-only
	STATUS mandatory
	DESCRIPTION
		"A control row to report the circuit state."
	::= { protconnectEntry 4 }

END
